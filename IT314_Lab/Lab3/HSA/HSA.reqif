# Specification Title

# Specification: Specification Document
- Description: Requirements Document

## REQ 1
Room Data
- Owner: Ayush Prajapati

### REQ 1.1
As a customer, it should give me details of rooms like AC or non AC, single bed or double bed.

### REQ 1.2
As a customer, it should display the rates of all types of available room.

### REQ 1.3
As a customer, I should be able to book room in advance or on the spot.

## REQ 2
Receptionist
- Owner: Shubham Patel

### REQ 2.1
As a receptionist, I need a database facility to store customer's details like name, address, contact, duration of stay, room type etc.

### REQ 2.2
As a receptionist, I need another database of advance booking customers with their name, duration of stay, room type, advance paid.

### REQ 2.3
As a receptionist, I need a facility which can allot room number to customer after booking and assig them unique token number

## REQ 3
Catering service
- Owner: Ayush Prajapati

### REQ 3.1
As a catering service manager, I can be able to input quantity and type of food items and token number for guests with corresponding date and time

### REQ 3.2
As a catering service manager, It should be able to generate bill for every customers with food name and price.

## REQ 4
Billing system
- Owner: Shubham Patel

### REQ 4.1
As a manager, I should be able to generate the entire bill of customer with payable amount.

### REQ 4.2
As a manager, I should be able to know the information of frequent guests so that I can provide them identity numbers which can be used to get special discount.
