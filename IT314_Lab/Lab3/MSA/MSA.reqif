# Specification Title

# Specification: Specification Document
- Description: Requirements Document

## REQ 1
Inventory manager
- Owner: Shubham Patel

### REQ 1.1
As a manager, I want a feature like database of medicines which can give information about medicine's a unique code number for medicine with medicine trade name, supplier vendor's details, medicine generic name, unit selling price, unit purchasin price, quantity etc.

### REQ 1.2
As a manager, I want feature that can update the stock, price etc. when new stock of medicines arrives.

### REQ 1.3
As a manager, I want a feature that can give information about expired medicines.

### REQ 1.4
As a manager, I want feature that gives information about thresold quantity of medicines and it should be updated in every week. It should generate a list of required medicines. When medicine quantity goes below thresold quantity, it should be added to the list.

## REQ 2
Data statistics
- Owner: Shubham Patel / Ayush Prajapati

### REQ 2.1
As a manager, It should give me graph of amout of medicines sold, profit per medicine for specific period.

### REQ 2.2
As a manager, I should be able to know the demand of medicine through graph so than I can order.

## REQ 3
Purchase and billing system
- Owner: Ayush Prajapati

### REQ 3.1
As a manager, I require a facility that can generate cash receipt for particular order. It should include medicine code number, name, quantity, price and total amount.

### REQ 3.2
As a manager, I require a cheque generating facility for vendors from whom I purchase medicines and it should verify details from me.

### REQ 3.3
As a manager, I require a database of my purchase orders from vendors.
